import FreeCAD
import PartDesign
#import PartDesignGui
import Sketcher
import math
import Part
import pandas as pd
import os
import sys
import Mesh



csv_path = sys.argv[1]
base_folder = os.path.dirname(csv_path)
valid_sample_path = os.path.join(base_folder, "samples.csv")
df = pd.read_csv(valid_sample_path)
os.chdir(base_folder)
output_folder = os.path.join(os.getcwd(), "geometries")

if not os.path.exists(output_folder):
    os.makedirs(output_folder)

for index, row in df.iterrows():
    chordlength = row['Chord Length']
    sweptangle = row['Sweep Angle']
    wingspan = row['Wing Span']
    trailingangle = row['Trailing Angle']
    root_thickness = row['Root Thickness']
    b=wingspan/2
    App.newDocument()
    App.activeDocument().addObject('PartDesign::Body','Body')
    App.ActiveDocument.getObject('Body').Label = 'Body'
    App.ActiveDocument.recompute()
    App.getDocument('Unnamed').getObject('Body').newObject('Sketcher::SketchObject','Sketch')
    App.getDocument('Unnamed').getObject('Sketch').AttachmentSupport = (App.getDocument('Unnamed').getObject('YZ_Plane'),[''])
    App.getDocument('Unnamed').getObject('Sketch').MapMode = 'FlatFace'
    App.ActiveDocument.recompute()
    App.getDocument('Unnamed').getObject('Sketch').addGeometry(Part.Point(App.Vector(-15.155131,0.000000,0)), True)
    App.getDocument('Unnamed').getObject('Sketch').addConstraint(Sketcher.Constraint('PointOnObject',0,1,-1)) 
    App.ActiveDocument.recompute()
    App.getDocument('Unnamed').getObject('Sketch').addGeometry(Part.Point(App.Vector(17.294466,0.000000,0)), True)
    App.ActiveDocument.recompute()
    App.getDocument('Unnamed').getObject('Sketch').addConstraint(Sketcher.Constraint('Symmetric',0,1,1,1,-1,1))
    App.ActiveDocument.recompute()
    App.getDocument('Unnamed').getObject('Sketch').addConstraint(Sketcher.Constraint('DistanceX',0,1,1,1,32.148740))
    App.getDocument('Unnamed').getObject('Sketch').setDatum(2,App.Units.Quantity(str(chordlength)))
    App.ActiveDocument.recompute()
    App.ActiveDocument.recompute()
    App.getDocument('Unnamed').getObject('Sketch').addGeometry(Part.Point(App.Vector(0.000000,15.260094,0)), True)
    App.getDocument('Unnamed').getObject('Sketch').addConstraint(Sketcher.Constraint('PointOnObject',2,1,-2)) 
    App.ActiveDocument.recompute()
    App.getDocument('Unnamed').getObject('Sketch').addGeometry(Part.Point(App.Vector(0.000000,-16.088818,0)), True)
    App.ActiveDocument.recompute()
    App.getDocument('Unnamed').getObject('Sketch').addConstraint(Sketcher.Constraint('Symmetric',2,1,3,1,-1,1))
    App.ActiveDocument.recompute()
    App.getDocument('Unnamed').getObject('Sketch').addConstraint(Sketcher.Constraint('DistanceY',3,1,2,1,31.611951))
    App.getDocument('Unnamed').getObject('Sketch').setDatum(5,App.Units.Quantity(str(root_thickness)))
    App.ActiveDocument.recompute()
    App.ActiveDocument.recompute()
    ActiveSketch = App.getDocument('Unnamed').getObject('Sketch')
    lastGeoId = len(ActiveSketch.Geometry)
    geoList = []
    geoList.append(Part.LineSegment(App.Vector(0.000000, 7.500000, 0.000000),App.Vector(50.000000, -0.000000, 0.000000)))
    App.getDocument('Unnamed').getObject('Sketch').addGeometry(geoList,False)
    del geoList
    constraintList = []
    constraintList = []
    constraintList.append(Sketcher.Constraint('Coincident', 4, 1, 2, 1))
    constraintList.append(Sketcher.Constraint('Coincident', 4, 2, 1, 1))
    App.getDocument('Unnamed').getObject('Sketch').addConstraint(constraintList)
    del constraintList
    App.ActiveDocument.recompute()
    ActiveSketch = App.getDocument('Unnamed').getObject('Sketch')
    lastGeoId = len(ActiveSketch.Geometry)
    geoList = []
    geoList.append(Part.LineSegment(App.Vector(50.000000, -0.000000, 0.000000),App.Vector(0.000000, -7.500000, 0.000000)))
    App.getDocument('Unnamed').getObject('Sketch').addGeometry(geoList,False)
    del geoList
    constraintList = []
    constraintList = []
    constraintList.append(Sketcher.Constraint('Coincident', 5, 1, 1, 1))
    constraintList.append(Sketcher.Constraint('Coincident', 5, 2, 3, 1))
    App.getDocument('Unnamed').getObject('Sketch').addConstraint(constraintList)
    del constraintList
    App.ActiveDocument.recompute()
    ActiveSketch = App.getDocument('Unnamed').getObject('Sketch')
    lastGeoId = len(ActiveSketch.Geometry)
    geoList = []
    geoList.append(Part.LineSegment(App.Vector(-50.000000, 0.000000, 0.000000),App.Vector(0.000000, 7.500000, 0.000000)))
    App.getDocument('Unnamed').getObject('Sketch').addGeometry(geoList,False)
    del geoList
    constraintList = []
    constraintList = []
    constraintList.append(Sketcher.Constraint('Coincident', 6, 1, 0, 1))
    constraintList.append(Sketcher.Constraint('Coincident', 6, 2, 2, 1))
    App.getDocument('Unnamed').getObject('Sketch').addConstraint(constraintList)
    del constraintList
    App.ActiveDocument.recompute()
    ActiveSketch = App.getDocument('Unnamed').getObject('Sketch')
    lastGeoId = len(ActiveSketch.Geometry)
    geoList = []
    geoList.append(Part.LineSegment(App.Vector(0.000000, -7.500000, 0.000000),App.Vector(-50.000000, 0.000000, 0.000000)))
    App.getDocument('Unnamed').getObject('Sketch').addGeometry(geoList,False)
    del geoList
    constraintList = []
    constraintList = []
    constraintList.append(Sketcher.Constraint('Coincident', 7, 1, 3, 1))
    constraintList.append(Sketcher.Constraint('Coincident', 7, 2, 0, 1))
    App.getDocument('Unnamed').getObject('Sketch').addConstraint(constraintList)
    del constraintList
    App.ActiveDocument.recompute()
    tipthickness=0.001
    rootsweeping=chordlength/2
    roottrailing=chordlength/2
    tipsweepingdistance=b*math.tan(math.radians(sweptangle))
    tiptrailingdistance=b*math.tan(math.radians(trailingangle))
    App.getDocument('Unnamed').getObject('Body').newObject('PartDesign::Plane','DatumPlane')
    App.getDocument('Unnamed').getObject('DatumPlane').AttachmentSupport = [(App.getDocument('Unnamed').getObject('XZ_Plane'),'')]
    App.getDocument('Unnamed').getObject('DatumPlane').MapMode = 'FlatFace'
    App.activeDocument().recompute()
    App.getDocument('Unnamed').getObject('DatumPlane').AttachmentOffset = App.Placement(App.Vector(0.0000000000, 0.0000000000, b),  App.Rotation(0.0000000000, 0.0000000000, 0.0000000000))
    App.getDocument('Unnamed').getObject('DatumPlane').MapReversed = False
    App.getDocument('Unnamed').getObject('DatumPlane').AttachmentSupport = [(App.getDocument('Unnamed').getObject('YZ_Plane'),'')]
    App.getDocument('Unnamed').getObject('DatumPlane').MapPathParameter = 0.000000
    App.getDocument('Unnamed').getObject('DatumPlane').MapMode = 'FlatFace'
    App.getDocument('Unnamed').getObject('DatumPlane').recompute()
    App.getDocument('Unnamed').getObject('Body').newObject('Sketcher::SketchObject','Sketch001')
    App.getDocument('Unnamed').getObject('Sketch001').AttachmentSupport = (App.getDocument('Unnamed').getObject('DatumPlane'),[''])
    App.getDocument('Unnamed').getObject('Sketch001').MapMode = 'FlatFace'
    App.ActiveDocument.recompute()
    App.getDocument('Unnamed').getObject('Sketch001').addGeometry(Part.Point(App.Vector(-25.093729,0.000000,0)), True)
    App.getDocument('Unnamed').getObject('Sketch001').addConstraint(Sketcher.Constraint('PointOnObject',0,1,-1)) 
    App.getDocument('Unnamed').getObject('Sketch001').addConstraint(Sketcher.Constraint('DistanceX',0,1,-1,1,25.093729))
    App.getDocument('Unnamed').getObject('Sketch001').setDatum(1,App.Units.Quantity(str(rootsweeping)))
    App.getDocument('Unnamed').getObject('Sketch001').addGeometry(Part.Point(App.Vector(24.770006,0.000000,0)), True)
    App.getDocument('Unnamed').getObject('Sketch001').addConstraint(Sketcher.Constraint('PointOnObject',1,1,-1)) 
    App.getDocument('Unnamed').getObject('Sketch001').addConstraint(Sketcher.Constraint('DistanceX',-1,1,1,1,24.770006))
    App.getDocument('Unnamed').getObject('Sketch001').setDatum(3,App.Units.Quantity(str(roottrailing)))
    App.getDocument('Unnamed').getObject('Sketch001').addGeometry(Part.Point(App.Vector(-11.975457,0.000000,0)), True)
    App.getDocument('Unnamed').getObject('Sketch001').addConstraint(Sketcher.Constraint('PointOnObject',2,1,-1)) 
    App.getDocument('Unnamed').getObject('Sketch001').addConstraint(Sketcher.Constraint('DistanceX',0,1,2,1,13.024543))
    App.getDocument('Unnamed').getObject('Sketch001').setDatum(5,App.Units.Quantity(str(tipsweepingdistance)))
    App.getDocument('Unnamed').getObject('Sketch001').addGeometry(Part.Point(App.Vector(16.674252,0.000000,0)), True)
    App.getDocument('Unnamed').getObject('Sketch001').addConstraint(Sketcher.Constraint('PointOnObject',3,1,-1)) 
    App.getDocument('Unnamed').getObject('Sketch001').addConstraint(Sketcher.Constraint('DistanceX',3,1,1,1,8.325748))
    App.getDocument('Unnamed').getObject('Sketch001').setDatum(7,App.Units.Quantity(str(tiptrailingdistance)))
    ActiveSketch = App.getDocument('Unnamed').getObject('Sketch001')
    lastGeoId = len(ActiveSketch.Geometry)
    constrGeoList = []
    constrGeoList.append(Part.LineSegment(App.Vector(-5.000000, 0.000000, 0.000000),App.Vector(15.000000, 0.000000, 0.000000)))
    App.getDocument('Unnamed').getObject('Sketch001').addGeometry(constrGeoList,True)
    del constrGeoList
    constraintList = []
    constraintList = []
    constraintList.append(Sketcher.Constraint('Coincident', 4, 1, 2, 1))
    constraintList.append(Sketcher.Constraint('Coincident', 4, 2, 3, 1))
    App.getDocument('Unnamed').getObject('Sketch001').addConstraint(constraintList)
    del constraintList
    ActiveSketch = App.getDocument('Unnamed').getObject('Sketch001')
    lastGeoId = len(ActiveSketch.Geometry)
    constrGeoList = []
    constrGeoList.append(Part.LineSegment(App.Vector(5.000000, 0.000000, 0.000000),App.Vector(5.120581, 4.705888, 0.000000)))
    App.getDocument('Unnamed').getObject('Sketch001').addGeometry(constrGeoList,True)
    del constrGeoList
    constraintList = []
    constraintList = []
    constraintList.append(Sketcher.Constraint('Symmetric', 4, 1, 4, 2, 5, 1))
    constraintList.append(Sketcher.Constraint('Vertical', 5))
    App.getDocument('Unnamed').getObject('Sketch001').addConstraint(constraintList)
    del constraintList
    App.getDocument('Unnamed').getObject('Sketch001').addGeometry(Part.Point(App.Vector(4.709064,-3.730186,0)), True)
    App.getDocument('Unnamed').getObject('Sketch001').addConstraint(Sketcher.Constraint('Symmetric',5,2,6,1,4))
    App.getDocument('Unnamed').getObject('Sketch001').addConstraint(Sketcher.Constraint('DistanceY',6,1,5,2,7.840572))
    App.getDocument('Unnamed').getObject('Sketch001').setDatum(13,App.Units.Quantity(str(tipthickness)))
    ActiveSketch = App.getDocument('Unnamed').getObject('Sketch001')
    lastGeoId = len(ActiveSketch.Geometry)
    geoList = []
    geoList.append(Part.LineSegment(App.Vector(-5.000000, 0.000000, 0.000000),App.Vector(5.000000, 2.500000, 0.000000)))
    App.getDocument('Unnamed').getObject('Sketch001').addGeometry(geoList,False)
    del geoList
    constraintList = []
    constraintList = []
    constraintList.append(Sketcher.Constraint('Coincident', 7, 1, 2, 1))
    constraintList.append(Sketcher.Constraint('Coincident', 7, 2, 5, 2))
    App.getDocument('Unnamed').getObject('Sketch001').addConstraint(constraintList)
    del constraintList
    ActiveSketch = App.getDocument('Unnamed').getObject('Sketch001')
    lastGeoId = len(ActiveSketch.Geometry)
    geoList = []
    geoList.append(Part.LineSegment(App.Vector(5.000000, 2.500000, 0.000000),App.Vector(15.000000, 0.000000, 0.000000)))
    App.getDocument('Unnamed').getObject('Sketch001').addGeometry(geoList,False)
    del geoList
    constraintList = []
    constraintList = []
    constraintList.append(Sketcher.Constraint('Coincident', 8, 1, 5, 2))
    constraintList.append(Sketcher.Constraint('Coincident', 8, 2, 3, 1))
    App.getDocument('Unnamed').getObject('Sketch001').addConstraint(constraintList)
    del constraintList
    ActiveSketch = App.getDocument('Unnamed').getObject('Sketch001')
    lastGeoId = len(ActiveSketch.Geometry)
    geoList = []
    geoList.append(Part.LineSegment(App.Vector(15.000000, 0.000000, 0.000000),App.Vector(5.000000, -2.500000, 0.000000)))
    App.getDocument('Unnamed').getObject('Sketch001').addGeometry(geoList,False)
    del geoList
    constraintList = []
    constraintList = []
    constraintList.append(Sketcher.Constraint('Coincident', 9, 1, 3, 1))
    constraintList.append(Sketcher.Constraint('Coincident', 9, 2, 6, 1))
    App.getDocument('Unnamed').getObject('Sketch001').addConstraint(constraintList)
    del constraintList
    ActiveSketch = App.getDocument('Unnamed').getObject('Sketch001')
    lastGeoId = len(ActiveSketch.Geometry)
    geoList = []
    geoList.append(Part.LineSegment(App.Vector(5.000000, -2.500000, 0.000000),App.Vector(-5.000000, 0.000000, 0.000000)))
    App.getDocument('Unnamed').getObject('Sketch001').addGeometry(geoList,False)
    del geoList
    constraintList = []
    constraintList = []
    constraintList.append(Sketcher.Constraint('Coincident', 10, 1, 6, 1))
    constraintList.append(Sketcher.Constraint('Coincident', 10, 2, 2, 1))
    App.getDocument('Unnamed').getObject('Sketch001').addConstraint(constraintList)
    del constraintList
    App.ActiveDocument.recompute()
    App.ActiveDocument.recompute()
    loft=App.getDocument('Unnamed').getObject('Body').newObject('PartDesign::AdditiveLoft','AdditiveLoft')
    App.getDocument('Unnamed').getObject('AdditiveLoft').Profile=App.getDocument('Unnamed').getObject('Sketch')
    App.getDocument('Unnamed').getObject('AdditiveLoft').Sections=App.getDocument('Unnamed').getObject('Sketch001')
    App.ActiveDocument.recompute()
    App.getDocument('Unnamed').getObject('Sketch').Visibility = False
    loft.Ruled=False
    loft.Closed=True
    App.ActiveDocument.recompute()
    App.getDocument('Unnamed').recompute()
    App.getDocument('Unnamed').getObject('Sketch').Visibility = False
    App.getDocument('Unnamed').getObject('Sketch001').Visibility = False
    App.getDocument('Unnamed').getObject('DatumPlane').Visibility = False

    save_path_fcstd = os.path.join(output_folder, f"Delta_Wing_Geometry_{index + 1}.FCStd")
    save_path_step = os.path.join(output_folder, f"Delta_Wing_Geometry_{index + 1}.step")

    App.getDocument('Unnamed').Body.Placement=App.Placement(App.Vector(0,0,0), App.Rotation(App.Vector(0.81,0.81,0),180), App.Vector(0,0,0))
    
    App.ActiveDocument.recompute()

    App.getDocument('Unnamed').saveAs(save_path_fcstd)

    step_part = App.getDocument('Unnamed').getObject('Body')
    Part.export([step_part], save_path_step)

    FreeCAD.closeDocument(App.getDocument('Unnamed').Name)
